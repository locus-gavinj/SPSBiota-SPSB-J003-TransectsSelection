FME workspace SPSB-J003_TransectsSelection_v2024.fmw

Parameters:
- AGOL_USER_AUTHORIZATION =
- excel_mpi_hrss_spreadsheet =   # INPUT MPI HRSS Excel Spreadsheet
- excel_mpi_hrss_sheetname =   # INPUT MPI HRSS Excel Sheet Name
- OUTPUT_FOLDER =   # OUTPUT Folder for Report
- STAGING_REFRESH = Yes   # Refresh Staging Table from Production
- INSPECTION_SEASON =   # Inspection Season
- INSPECTION_ROUND =   # Inspection Round

Creator
    GEOMTYPE = Geometry Object
    NUM = 1
    CREATED -> DateTimeStamper
DateTimeStamper
    DATETIME_ATTR = _timestamp
    INCLUDE_FRAC_SECONDS = NO
    INCLUDE_OFFSET = NO
    STAMP_TYPE = datetime
    TIMEZONE = utc
    -> FeatureReader_2 [INITIATOR]
Note: MPI HRSS Spreasheet
FeatureReader_2
    ATTRIBUTES = "HRSS R1 Plan","""SA2_2023 Code"",""SA2_2023 Name"",Transects"
    ATTR_ACCUM_MODE = Merge Initiator and Result
    ATTR_CONFLICT_RES = Use Result
    ATTR_IGNORE_NULLS = No
    CLIP_TO_ENVELOPE = NO
    COMBINE_GEOM = Use Result
    DATASET = $(excel_mpi_hrss_spreadsheet)
    FORMAT = XLSXR
    INITIATOR_FIRST_OUTPUT = default
    INTERACT = NONE
    ORDER_RESULTS = No
    OUTPUT_ADD_SCHEMA_ATTRIBUTES = NO
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = C:\Users\GavinJeter\OneDrive - Locus Limited\Clients - Documents\SPS Biota\SPSB-J003 - Transects Selection FME Workspace\Input\HRSS Model Output Example 2025-26 - Rnd 1 - GJJ.xlsx
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    <SCHEMA> -> TestFilter_10
    <OTHER> -> ParameterFetcher_2
    INITIATOR -> Junction_40
    <REJECTED> -> AttributeCreator_16
TestFilter_10
    DEFAULT_VALUE = <UNFILTERED>
    PASSED_TEST_GROUP_OUTPUT = FIRST
    TEST_LIST:
      "BOOL_OP,AND,COMPOSITE_TEST,""""""1 AND 2 AND 3"""""",TEST_CLAUSE,TEST @Value(attribute{0}.name) = SA2_2023 Code
      TEST @Value(attribute{1}.name) = SA2_2023 Name
      TEST @Value(attribute{2}.name) = Transects",PASS_Spaces,"BOOL_OP,AND,COMPOSITE_TEST,""""""1 AND 2 AND 3"""""",TEST_CLAUSE,TEST @Value(attribute{0}.name) = SA2_2023_Code
      TEST @Value(attribute{1}.name) = SA2_2023_Name
      TEST @Value(attribute{2}.name) = Transects",PASS_Underscores
    PASS_Spaces -> AttributeKeeper_6
    PASS_Spaces -> ArcGISOnlineConnector_2
    PASS_Underscores -> AttributeKeeper_7
    PASS_Underscores -> ArcGISOnlineConnector_2
    <UNFILTERED> -> AttributeCreator_29
Note: UPDATE SPS BIOTA AGOL
AttributeKeeper_6
    CREATE_BULK_MODE_FEATURES = NO
    -> FeatureMerger_16 [REQUESTOR]
AttributeKeeper_7
    CREATE_BULK_MODE_FEATURES = NO
    -> FeatureMerger_17 [REQUESTOR]
Note: Error
AttributeCreator_29
    ATTR_TABLE:
      SET_TO errorType (buffer) = TestFilter_10 - MPI HRSS Sheet Schema
      SET_TO errorMessage (buffer) = The Spreadsheet schema is not valid.

        SA2_2023 Code,SA2_2023 Name,Transects
        -or-
        SA2_2023_Code,SA2_2023_Name,Transects
    -> Junction_45
Junction_45
    -> Junction_46
Note: Expose Spreadsheet Attributes - Spaces
AttributeExposer
    ATTR_TABLE = "SA2_2023 Code",uint32,"SA2_2023 Name",varchar(44),Transects,uint8,fme_feature_type,
    -> BulkAttributeRenamer_4
Note: Replace all [space] with Underscore
BulkAttributeRenamer_4
    ATTRCHOICE_ACTION = NONPROTECTEDFME
    CASE_DISP = YES
    MODE_CHOICE = RENAME
    PATTERN_ACTION_DISP = STRINGREPLACE
    REPLACE_PATTERN = " "
    REPLACE_STR = _
    ATTRCHOICE = All Attributes
    -> TestFilter_12
Note: Expose Spreadsheet Attributes - Underscores
Note: UPDATE SPS BIOTA AGOL
AttributeExposer_3
    ATTR_TABLE = SA2_2023_Code,uint32,SA2_2023_Name,varchar(44),Transects,uint8,fme_feature_type,
    -> TestFilter_12
Note: Validate Spreadsheet - Testing All Attributes Exist
TestFilter_12
    DEFAULT_VALUE = <UNFILTERED>
    PASSED_TEST_GROUP_OUTPUT = FIRST
    TEST_LIST:
      "BOOL_OP,AND,COMPOSITE_TEST,""""""1 AND 2 AND 3"""""",TEST_CLAUSE,TEST SA2_2023_Code ATTRIBUTE_HAS_A_VALUE ""
      TEST SA2_2023_Name ATTRIBUTE_HAS_A_VALUE ""
      TEST Transects ATTRIBUTE_HAS_A_VALUE """,PASS
    PASS -> FeatureMerger_15 [REQUESTOR]
    <UNFILTERED> -> AttributeCreator_28
Note: Error
AttributeCreator_28
    ATTR_TABLE:
      SET_TO errorType (buffer) = TestFilter_12 - Transects Selection
      SET_TO errorMessage (buffer) = Input Spreadsheet Validation FAILED

        Verify the input spreadsheet schema matches:
        - SA2_2023 Code
        - SA2_2023 Name
        - Transects

        Verify each spreadsheet row and column has data. For example:
        SA2_2023 Code | SA2_2023 Name | Transects
        100100 | North Cape | 0
    -> Junction_44
Note: Error
AttributeCreator_16
    ATTR_TABLE:
      SET_TO errorType (buffer) = FeatureReader_2 - MPI HRSS Spreadsheet
      SET_TO errorMessage (buffer) = Error Reading Spreadsheet

        Error Type: @Value(errorType)
        Error: @Value(_reader_error)
        Rejection Code: @Value(fme_rejection_code)
    -> Junction_41
Junction_40
    -> FeatureReader_7 [INITIATOR]
Note: PRODUCTION / SPS Biota AGOL - "HRSS SA2 Transect Plan" / This layer is the AGOL version of the MPI HRSS input spreadsheet
FeatureReader_7
    ATTRIBUTES = "HRSS SA2 Transect Plan","SA2_2023_Code,SA2_2023_Name,Transects,FID"
    ATTR_ACCUM_MODE = Only Use Result
    CLIP_TO_ENVELOPE = NO
    COMBINE_GEOM = Use Result
    FEATURETYPES = HRSS SA2 Transect Plan
    FORMAT = SAFE.ESRI-AGOL.ARCGISFEATURESERVICE
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = $(AGOL_USER_AUTHORIZATION)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = HRSS SA2 Target Table_Current(a5d5f4debee94a79a8e07f8c8bf0ac5a)
    SAFE.ESRI-AGOL.ARCGISFEATURESERVICE_FOLDER_NAME = Gavin Scratch
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = USER
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    HRSS SA2 Transect Plan -> AttributeKeeper_8
    <REJECTED> -> AttributeCreator_35
AttributeKeeper_8
    CREATE_BULK_MODE_FEATURES = NO
    KEEP_ATTRS = FID,SA2_2023_Code
    -> FeatureMerger_15 [SUPPLIER]
Note: Merge New Transect Plan to AGOL "HRSS SA2 Transect Plan" table on SA2 Code to get OBJECTID
FeatureMerger_15
    ATTR_ACCUM_MODE = Merge Supplier
    ATTR_CONFLICT_RES_LOOKUP = REQUESTOR_IF_CONFLICT
    IGNORE_NULLS = No
    JOIN_KEYS = @Value(SA2_2023_Code) @Value(SA2_2023_Code) AUTO
    MERGE_TYPE = Attributes Only
    PROCESS_DUPS = NO
    REJECT_NULL_MISSING_KEYS = No
    SUPPLIERS_FIRST = No
    ATTR_CONFLICT_RES = Use Requestor
    MERGED -> FeatureWriter_2 [UnmergedRequestor]
    <REJECTED> -> AttributeCreator_33
Note: UPDATE SPS BIOTA AGOL
Note: Update Transect Layer / Scheduled_for_Round scheduled_for_round1, 2, 3
FeatureWriter_2
    DATASET_ATTR = _dataset
    FEATURE_TYPE_LIST_ATTR = _feature_types
    FORMAT = SAFE.ESRI-AGOL.ARCGISFEATURESERVICE
    SAFE.ESRI-AGOL.ARCGISFEATURESERVICE_AGOL_AUTH_NC = $(AGOL_USER_AUTHORIZATION)
    SAFE.ESRI-AGOL.ARCGISFEATURESERVICE_ALWAYS_CREATE_FEATURE_TYPES = NO
    SAFE.ESRI-AGOL.ARCGISFEATURESERVICE_APPEND_FORMAT = geojson
    SAFE.ESRI-AGOL.ARCGISFEATURESERVICE_ASYNC_WRITE = NO
    SAFE.ESRI-AGOL.ARCGISFEATURESERVICE_FEATURES_PER_REQUEST = 1000
    SAFE.ESRI-AGOL.ARCGISFEATURESERVICE_FEATURE_SERVICE_HANDLING = USE_EXISTING
    SAFE.ESRI-AGOL.ARCGISFEATURESERVICE_FEATURE_SERVICE_WITH_ID = HRSS SA2 Target Table_Current(a5d5f4debee94a79a8e07f8c8bf0ac5a)
    SAFE.ESRI-AGOL.ARCGISFEATURESERVICE_FOLDER_NAME = Gavin Scratch
    SAFE.ESRI-AGOL.ARCGISFEATURESERVICE_SITE_SOURCE_TYPE = USER
    SAFE.ESRI-AGOL.ARCGISFEATURESERVICE_URL_TYPE = AGOL
    SAFE.ESRI-AGOL.ARCGISFEATURESERVICE_USE_GLOBAL_ID = NO
    SAFE.ESRI-AGOL.ARCGISFEATURESERVICE_VERIFY_HTTPS = WEB_CONN
    TOTAL_FEATURES_WRITTEN_ATTR = _total_features_written
    SUMMARY -> FeatureReader_5 [INITIATOR]
Note: UPDATE SPS BIOTA AGOL
Note: PRODUCTION Table / SPS Biota AGOL - "HRSS SA2 Transect Plan" / This layer is the AGOL version of the MPI HRSS input spreadsheet
FeatureReader_5
    ATTR_ACCUM_MODE = Only Use Result
    CLIP_TO_ENVELOPE = NO
    COMBINE_GEOM = Use Result
    FEATURETYPES = HRSS SA2 Transect Plan
    FORMAT = SAFE.ESRI-AGOL.ARCGISFEATURESERVICE
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = $(AGOL_USER_AUTHORIZATION)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = HRSS SA2 Target Table_Current(a5d5f4debee94a79a8e07f8c8bf0ac5a)
    SAFE.ESRI-AGOL.ARCGISFEATURESERVICE_FOLDER_NAME = Gavin Scratch
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = USER
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    <OTHER> -> AttributeExposer_2
    <REJECTED> -> AttributeCreator_2
Note: Expose Hosted Table Attributes
AttributeExposer_2
    ATTR_TABLE = SA2_2023_Code,,SA2_2023_Name,,Transects,
    -> AttributeManager_14
AttributeManager_14
    ATTR_TABLE:
      RENAME_SET_VALUE SA2_2023_Code > SA2_2023 Code (varchar(200))
      RENAME_SET_VALUE SA2_2023_Name > SA2_2023 Name (varchar(200))
    USER_EXPOSED_ATTRIBUTES = fme_feature_type
    -> StatisticsCalculator_2
Note: Last Feature Trigger
Sampler
    MODE = ORIGINAL
    RATE = 1
    SAMPLE_TYPE_MULTIPLIER = 0
    SAMPLE_MODE = No
    SAMPLE_TYPE_LONG = Last N Features
    SAMPLED -> AttributeCreator
    SAMPLED -> TestFilter_4
    NOT_SAMPLED -> AttributeCreator
Note: UPDATE SPS BIOTA AGOL
Note: Refresh Staging Table
Note: UPDATE SPS BIOTA AGOL
TestFilter_4
    DEFAULT_VALUE = <UNFILTERED>
    PASSED_TEST_GROUP_OUTPUT = FIRST
    TEST_LIST = "BOOL_OP,OR,COMPOSITE_TEST,""""""1"""""",TEST_CLAUSE,TEST $(STAGING_REFRESH) = Yes",Yes
    Yes -> FeatureReader_3 [INITIATOR]
    <UNFILTERED> -> FeatureReader_6 [INITIATOR]
Note: UPDATE SPS BIOTA AGOL
Note: UPDATE SPS BIOTA AGOL
Note: STAGING / SPS Biota AGOL - SA2_2023 Data
FeatureReader_6
    ATTRIBUTES = "SA2 2023 HRSS Staging","OBJECTID,SA22023_V1,SA22023__1,SA22023__2,Count_Transects,Contain_Transects,Required_Transects_MPI,New_Transects_MPI,Exiting_Selected_Transects,SA2_Inspection_Status_SPS,Active_SA2_MPI,SA2_Comments,Crosby,Crosby_Code,Who,SA2_Number,globalid,Shape__Area,Shape__Length,SA2_Transect_Selection_Completed,Outstanding_Transects"
    ATTR_ACCUM_MODE = Only Use Result
    CLIP_TO_ENVELOPE = NO
    COMBINE_GEOM = Use Result
    FEATURETYPES = SA2 2023 HRSS Staging
    FORMAT = SAFE.ESRI-AGOL.ARCGISFEATURESERVICE
    GEOMETRY_TYPES = "SA2 2023 HRSS Staging",""",fme_area"""
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = $(AGOL_USER_AUTHORIZATION)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = SA2 2023 HRSS Staging(615650d4be7a47189a304aeef94cbebc)
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_GROUP_ID = 02af8fa42acc4054a20f72f705d115db
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    SA2 2023 HRSS Staging -> AttributeKeeper
    <REJECTED> -> AttributeCreator_18
Note: Keep OBJECTID, SA22023_V1, Count_Transects
AttributeKeeper
    CREATE_BULK_MODE_FEATURES = NO
    KEEP_ATTRS = OBJECTID,SA22023_V1,Count_Transects
    -> AttributeRounder
Note: Trim any zeros
AttributeRounder
    PLACES = 0
    ROUND_TYPE_TCL = round
    SRC_ATTRS = SA22023_V1
    ROUND_TYPE = Nearest
    -> FeatureMerger [SUPPLIER]
Note: Error
AttributeCreator_18
    ATTR_TABLE:
      SET_TO errorType (buffer) = FeatureReader_5
      SET_TO errorMessage (buffer) = Error Pulling Staging Data

        Error Type: @Value(errorType)
        Reader Error: @Value(_reader_error)
        Rejection Code: @Value(fme_rejection_code)
    -> Junction_11
Note: Active = Yes/No
AttributeCreator
    ATTR_TABLE = SET_TO mpi_schedule (varchar(200)) = FME_CONDITIONAL:DEFAULT_VALUE'@Abort(ERROR with Transect Value from HRSS Spreadsheet)'BOOL_OP;OR;COMPOSITE_TEST;1;TEST @Value(Transects) = 0'No'BOOL_OP;OR;COMPOSITE_TEST;1;TEST @Value(Transects) > 0'Yes'FME_NUM_CONDITIONS3___
    -> FeatureMerger [REQUESTOR]
Note: Merge HRSS List to Refreshed SA2 Table Transect Counts
FeatureMerger
    ATTR_ACCUM_MODE = Merge Supplier
    ATTR_CONFLICT_RES_LOOKUP = REQUESTOR_IF_CONFLICT
    IGNORE_NULLS = No
    JOIN_KEYS = @Value(SA2_2023 Code) @Value(SA22023_V1) AUTO
    MERGE_TYPE = Attributes Only
    PROCESS_DUPS = NO
    REJECT_NULL_MISSING_KEYS = No
    SUPPLIERS_FIRST = No
    ATTR_CONFLICT_RES = Use Requestor
    MERGED -> FeatureMerger_2 [REQUESTOR]
    UNMERGED_REQUESTOR -> TestFilter_2
    <REJECTED> -> AttributeCreator_7
Note: Error
AttributeCreator_7
    ATTR_TABLE:
      SET_TO errorType (buffer) = FeatureMerger - SPS Biota AGOL SA2_2023 to MPI HRSS Spreadsheet
      SET_TO errorMessage (buffer) = Error: @Value(errorType)
        FME Rejection Code: @Value(fme_rejection_code)

        Notify FME Specialist
    -> Junction_12
Junction_29
    -> Junction_32
Junction_32
    -> __WARNINGS___
__WARNINGS___: Inspector [off]
Note: Open the Gate - If no Errors, let pass
FeatureMerger_2
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    UNMERGED_REQUESTOR -> AttributeManager_11
    <REJECTED> -> AttributeCreator_19
Note: ObjectID, Active, Required_Transects_MPI, New_Transects_MPI, Exiting_Selected_Transects, SA2_Inspection_Status_SPS
AttributeManager_11
    ATTR_TABLE:
      RENAME_SET_VALUE Transects > Required_Transects_MPI (varchar(200))
      SET_TO New_Transects_MPI (varchar(200)) = FME_CONDITIONAL:DEFAULT_VALUE'0'BOOL_OP;AND;COMPOSITE_TEST;1 AND 2 AND 3;TEST @Value(Required_Transects_MPI) > 0;TEST @Value(Required_Transects_MPI) > @Value(Count_Transects);TEST Count_Transects ATTRIBUTE_VALUE_NULL _FME_BLANK_STRING_'@Evaluate(@Value(Required_Transects_MPI)-0)'BOOL_OP;AND;COMPOSITE_TEST;1 AND 2;TEST @Value(Required_Transects_MPI) > 0;TEST @Value(Required_Transects_MPI) > @Value(Count_Transects)'@Evaluate(@Value(Required_Transects_MPI)-@Value(Count_Transects))'FME_NUM_CONDITIONS3___
      SET_TO Exiting_Selected_Transects (real64) = @Value(Required_Transects_MPI)
      REMOVE SA2_2023 Code (varchar(200))
      REMOVE SA2_2023 Name (varchar(200))
      REMOVE Count_Transects (int32)
    -> Junction_37
    -> TestFilter_7
Note: SA2 2023 HRSS Staging Layer
Junction_37
    -> FeatureMerger_12 [REQUESTOR]
Note: Filter - Active = Yes
TestFilter_7
    DEFAULT_VALUE = <UNFILTERED>
    PASSED_TEST_GROUP_OUTPUT = FIRST
    TEST_LIST = "BOOL_OP,OR,COMPOSITE_TEST,""""""1"""""",TEST_CLAUSE,TEST @Value(mpi_schedule) = Yes",MPI_Schedule
    MPI_Schedule -> BulkAttributeRenamer_3
Note: UPDATE SPS BIOTA AGOL
Note: Rename with prefix sa2_
BulkAttributeRenamer_3
    ATTRCHOICE_ACTION = NONPROTECTEDFME
    MODE_CHOICE = RENAME
    PATTERN_ACTION_DISP = ADDPREFIX
    REPLACE_STR = sa2_
    ATTRCHOICE = All Attributes
    -> Sampler_4
    -> Junction
Note: Last Feature Trigger
Sampler_4
    MODE = ORIGINAL
    RATE = 1
    SAMPLE_TYPE_MULTIPLIER = 0
    SAMPLE_MODE = No
    SAMPLE_TYPE_LONG = Last N Features
    SAMPLED -> FeatureReader [INITIATOR]
Note: All Transects for Final Write
Junction_4
    -> AttributeKeeper_10
AttributeKeeper_10
    CREATE_BULK_MODE_FEATURES = NO
    KEEP_ATTRS = created_date,created_user,Crosby,globalid,Host_Count,inspection_date,inspection_stage,inspection_status,last_edited_date,last_edited_user,objectid,personal_security,R1_Inspection_Status,R2_Inspection_Status,R3_Inspection_status,Round_1_Date,Round_2_Date,Round_3_Date,rsa_abbreviation,SA_Name,SA2_Number,safety_comments,scheduled_for_round1,scheduled_for_round2,scheduled_for_round3,Shape__Length,surveyorid,traffic_details,transect_comments,transect_id,transect_status,tvd_quality
    -> FeatureMerger_9 [REQUESTOR]
Junction
    -> FeatureMerger_3 [SUPPLIER]
Note: Merge Transects to SA2 via SA2_Number
FeatureMerger_3
    ATTR_ACCUM_MODE = Merge Supplier
    ATTR_CONFLICT_RES_LOOKUP = REQUESTOR_IF_CONFLICT
    IGNORE_NULLS = No
    JOIN_KEYS = @Value(transects_SA2_Number) @Value(sa2_SA22023_V1) AUTO
    MERGE_TYPE = Attributes Only
    PROCESS_DUPS = NO
    REJECT_NULL_MISSING_KEYS = No
    SUPPLIERS_FIRST = Yes
    ATTR_CONFLICT_RES = Use Requestor
    MERGED -> Sampler_6
    UNUSED_SUPPLIER -> Junction_3
    <REJECTED> -> AttributeCreator_32
Note: Last Feature Trigger
Note: UPDATE SPS BIOTA AGOL
Sampler_3
    MODE = ORIGINAL
    RATE = 1
    SAMPLE_TYPE_MULTIPLIER = 0
    SAMPLE_MODE = No
    SAMPLE_TYPE_LONG = Last N Features
    SAMPLED -> FeatureReader_4 [INITIATOR]
Note: Merge Vegetation to Transects on parent_id (global_id of Transect)
FeatureMerger_4
    ATTR_ACCUM_MODE = Merge Supplier
    ATTR_CONFLICT_RES_LOOKUP = REQUESTOR_IF_CONFLICT
    IGNORE_NULLS = No
    JOIN_KEYS = @Value(vegetation_parentid) @Value(vegetation_parentid) AUTO
    MERGE_TYPE = Attributes Only
    PROCESS_DUPS = NO
    REJECT_NULL_MISSING_KEYS = No
    SUPPLIERS_FIRST = Yes
    ATTR_CONFLICT_RES = Use Requestor
    MERGED -> StringSearcher_2
    MERGED -> Aggregator_2 [off]
    UNUSED_SUPPLIER -> Junction_5
    <REJECTED> -> AttributeCreator_20
Note: Transect - No Vegetation
Junction_5
    -> StringSearcher_2
    -> AttributeManager_8
Note: Create Validation Attributes
AttributeManager_2
    ATTR_TABLE:
      SET_TO transects_HRSS-Spreadsheet (varchar(200)) = @Value(sa2_Required_Transects_MPI)
      SET_TO transects_AGOL_SA2_2023_HRSS_Locus (varchar(200)) = @Value(sa2_SA22023_V1.total_count)
    -> Sorter_3
Note: Sort By: Priority then Inspection Date (Oldest First)
Sorter_3
    GROUP_BY = sa2_SA22023_V1
    SORT_PARM = vegetation_Priority_Number NUMERIC ASCENDING transects_inspection_date NATURAL ASCENDING
    SORTED -> Counter
Note: Priority Order
Counter
    CNT_ATTR = _order_priority_transect
    GROUP_BY = sa2_SA22023_V1
    SCOPE = Local
    START = 1
    -> AttributeCreator_9
Note: Scheduled for Round / Scheduled for Round 1, 2, 3
AttributeCreator_9
    ATTR_TABLE:
      SET_TO automated_Scheduled_for_Round (varchar(200)) = FME_CONDITIONAL:DEFAULT_VALUE'No'BOOL_OP;AND;COMPOSITE_TEST;1;TEST @Value(_order_priority_transect) <= @Value(transects_HRSS-Spreadsheet)'Yes'FME_NUM_CONDITIONS2___
      SET_TO Scheduled_for_Round (varchar(200)) = FME_CONDITIONAL:DEFAULT_VALUE'No'BOOL_OP;AND;COMPOSITE_TEST;1 AND 2;TEST @Value(_order_priority_transect) <= @Value(transects_HRSS-Spreadsheet);TEST @Value(vegetation_Priority_Number) < 100'Yes'FME_NUM_CONDITIONS2___
      SET_TO scheduled_for_round1 (varchar(200)) = FME_CONDITIONAL:DEFAULT_VALUE'@Value(transects_scheduled_for_round1)'BOOL_OP;OR;COMPOSITE_TEST;1;TEST $(INSPECTION_ROUND) = 1'@Value(Scheduled_for_Round)'FME_NUM_CONDITIONS2___
      SET_TO scheduled_for_round2 (varchar(200)) = FME_CONDITIONAL:DEFAULT_VALUE'@Value(transects_scheduled_for_round2)'BOOL_OP;OR;COMPOSITE_TEST;1;TEST $(INSPECTION_ROUND) = 1'FME_NULL_VALUE'BOOL_OP;OR;COMPOSITE_TEST;1;TEST $(INSPECTION_ROUND) = 2'@Value(Scheduled_for_Round)'FME_NUM_CONDITIONS3___
      SET_TO scheduled_for_round3 (varchar(200)) = FME_CONDITIONAL:DEFAULT_VALUE'@Value(Scheduled_for_Round)'BOOL_OP;OR;COMPOSITE_TEST;1;TEST $(INSPECTION_ROUND) = 1'FME_NULL_VALUE'BOOL_OP;OR;COMPOSITE_TEST;1;TEST $(INSPECTION_ROUND) = 2'FME_NULL_VALUE'FME_NUM_CONDITIONS3___
    -> TestFilter_5
Note: Filter Scheduled = Yes
TestFilter_5
    DEFAULT_VALUE = <UNFILTERED>
    PASSED_TEST_GROUP_OUTPUT = FIRST
    TEST_LIST = "BOOL_OP,OR,COMPOSITE_TEST,""""""1"""""",TEST_CLAUSE,TEST @Value(Scheduled_for_Round) = Yes",Scheduled,"BOOL_OP,AND,COMPOSITE_TEST,""""""1"""""",TEST_CLAUSE,TEST @Value(automated_Scheduled_for_Round) = Yes",Automated
    Scheduled -> StatisticsCalculator_3
    Scheduled -> AttributeKeeper_2
    Scheduled -> AttributeManager_5
    Scheduled -> StatisticsCalculator_8
    Automated -> StatisticsCalculator_7
Note: Calculate Selected Counts for Selection Status = Complete
StatisticsCalculator_8
    ATTR_ACCUM_MODE = None
    CALCULATION_MODE = LEXICAL
    FEAT_STATS = Scheduled_for_Round,LEXICAL,,,COUNT,<Unused>,<Unused>,,,,<Unused>,<Unused>,<Unused>,,
    GROUP_BY = sa2_SA22023_V1
    SUMMARY -> AttributeRenamer_5
Note: SA22023_V1 / transects_selected_final
AttributeRenamer_5
    ATTR_TABLE:
      RENAME_SET_DEFAULT sa2_SA22023_V1 > SA22023_V1
      RENAME_SET_DEFAULT Scheduled_for_Round.total_count > transects_selected_final
    KEEP_RENAMED_ONLY = no
    MISSING_INPUT_ATTRS = REMOVE
    -> NullAttributeMapper
Note: transects_selected_final - Set null to Zero
NullAttributeMapper
    ATTRCHOICE_ACTION = SELECTED
    ATTRLIST = transects_selected_final
    NEW_VALUE = 0
    NULL_TREATMENT_LU = SETVALUE
    SOURCE_ATTR_VAL_LU = SETNULL EMPTY MISSINGATTR
    ATTRCHOICE = Selected Attributes
    NULL_TREATMENT = New Value
    SOURCE_ATTR_VAL = Null Empty "Missing (Selected Attributes Only)"
    -> FeatureMerger_12 [SUPPLIER]
Note: Merge SA2 Information to Final Transect Selection Counts
FeatureMerger_12
    ATTR_ACCUM_MODE = Merge Supplier
    ATTR_CONFLICT_RES_LOOKUP = REQUESTOR_IF_CONFLICT
    IGNORE_NULLS = No
    JOIN_KEYS = @Value(SA22023_V1) @Value(SA22023_V1) AUTO
    MERGE_TYPE = Attributes Only
    PROCESS_DUPS = NO
    REJECT_NULL_MISSING_KEYS = No
    SUPPLIERS_FIRST = No
    ATTR_CONFLICT_RES = Use Requestor
    MERGED -> AttributeManager_13
    UNMERGED_REQUESTOR -> AttributeManager_13
    <REJECTED> -> AttributeCreator_38
Note: SA2_Transect_Selection_Completed / Outstanding_Transects
AttributeManager_13
    ATTR_TABLE:
      SET_TO SA2_Transect_Selection_Completed (varchar(200)) = FME_CONDITIONAL:DEFAULT_VALUE'Not Completed'BOOL_OP;AND;COMPOSITE_TEST;1 AND 2;TEST @Value(Required_Transects_MPI) > 0;TEST @Value(Required_Transects_MPI) = @Value(transects_selected_final)'Completed'FME_NUM_CONDITIONS2___
      SET_TO Outstanding_Transects (int16) = FME_CONDITIONAL:DEFAULT_VALUE'0'BOOL_OP;AND;COMPOSITE_TEST;1;TEST @Value(Required_Transects_MPI) > 0'@Evaluate(@Value(Required_Transects_MPI)-@Value(transects_selected_final))'FME_NUM_CONDITIONS2___
    -> FeatureWriter_7 [UnmergedRequestor]
    -> _SA2_2023_HRSS_Staging
_SA2_2023_HRSS_Staging: Inspector [off]
Note: Update _STAGING Layer / Active, Required_Transects, New_Transects, Tota_Transects, Selection_Status
Note: UPDATE SPS BIOTA AGOL
FeatureWriter_7
    DATASET_ATTR = _dataset
    FEATURE_TYPE_LIST_ATTR = _feature_types
    FORMAT = SAFE.ESRI-AGOL.ARCGISFEATURESERVICE
    SAFE.ESRI-AGOL.ARCGISFEATURESERVICE_AGOL_AUTH_NC = $(AGOL_USER_AUTHORIZATION)
    SAFE.ESRI-AGOL.ARCGISFEATURESERVICE_ALWAYS_CREATE_FEATURE_TYPES = NO
    SAFE.ESRI-AGOL.ARCGISFEATURESERVICE_APPEND_FORMAT = featureCollection
    SAFE.ESRI-AGOL.ARCGISFEATURESERVICE_ASYNC_WRITE = NO
    SAFE.ESRI-AGOL.ARCGISFEATURESERVICE_FEATURES_PER_REQUEST = 1000
    SAFE.ESRI-AGOL.ARCGISFEATURESERVICE_FEATURE_SERVICE_HANDLING = USE_EXISTING
    SAFE.ESRI-AGOL.ARCGISFEATURESERVICE_FEATURE_SERVICE_WITH_ID = SA2 2023 HRSS Staging(615650d4be7a47189a304aeef94cbebc)
    SAFE.ESRI-AGOL.ARCGISFEATURESERVICE_GROUP_ID = 02af8fa42acc4054a20f72f705d115db
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_GLOBAL_ID = NO
    SAFE.ESRI-AGOL.ARCGISFEATURESERVICE_VERIFY_HTTPS = WEB_CONN
    TOTAL_FEATURES_WRITTEN_ATTR = _total_features_written
Note: Error
AttributeCreator_38
    ATTR_TABLE:
      SET_TO errorType (buffer) = FeatureMerger_12 - Merging Final Selected Transect numbers to SA2 Failed
      SET_TO errorMessage (buffer) = FME Rejection Code: @Value(fme_rejection_code)

        Error merging final Transect selections to SA2. Notify FME Specialist
    -> Junction_51
Note: Error
Junction_51
    -> Junction_52
Junction_52
    -> Junction_53
Junction_53
    -> Junction_54
FeatureMerger_9
    ATTR_ACCUM_MODE = Merge Supplier
    ATTR_CONFLICT_RES_LOOKUP = SUPPLIER_IF_CONFLICT
    IGNORE_NULLS = No
    JOIN_KEYS = @Value(objectid) @Value(objectid) AUTO
    MERGE_TYPE = Attributes Only
    PROCESS_DUPS = NO
    REJECT_NULL_MISSING_KEYS = No
    SUPPLIERS_FIRST = No
    ATTR_CONFLICT_RES = Use Supplier
    MERGED -> AttributeKeeper_3
    UNMERGED_REQUESTOR -> AttributeManager_7
    <REJECTED> -> AttributeCreator_24
Note: Set all other Transect Schedules
AttributeManager_7
    ATTR_TABLE:
      SET_TO scheduled_for_round1 (varchar(255)) = FME_CONDITIONAL:DEFAULT_VALUE'_FME_NO_OP_'BOOL_OP;OR;COMPOSITE_TEST;1;TEST $(INSPECTION_ROUND) = 1'No'FME_NUM_CONDITIONS2___
      SET_TO scheduled_for_round2 (varchar(255)) = FME_CONDITIONAL:DEFAULT_VALUE'_FME_NO_OP_'BOOL_OP;OR;COMPOSITE_TEST;1;TEST $(INSPECTION_ROUND) = 1'FME_NULL_VALUE'BOOL_OP;OR;COMPOSITE_TEST;1;TEST $(INSPECTION_ROUND) = 2'No'FME_NUM_CONDITIONS3___
      SET_TO scheduled_for_round3 (varchar(255)) = FME_CONDITIONAL:DEFAULT_VALUE'_FME_NO_OP_'BOOL_OP;OR;COMPOSITE_TEST;1;TEST $(INSPECTION_ROUND) = 1'FME_NULL_VALUE'BOOL_OP;OR;COMPOSITE_TEST;1;TEST $(INSPECTION_ROUND) = 2'FME_NULL_VALUE'BOOL_OP;OR;COMPOSITE_TEST;1;TEST $(INSPECTION_ROUND) = 3'No'FME_NUM_CONDITIONS4___
      SET_TO Scheduled_for_Round (varchar(2)) = No
    -> AttributeKeeper_3
AttributeKeeper_3
    CREATE_BULK_MODE_FEATURES = NO
    KEEP_ATTRS = objectid,Scheduled_for_Round,scheduled_for_round1,scheduled_for_round2,scheduled_for_round3
    -> FeatureMerger_10 [REQUESTOR]
Note: Error
AttributeCreator_24
    ATTR_TABLE:
      SET_TO errorType (buffer) = FeatureMerger_9 - Merging Scheduled onto Transect Features
      SET_TO errorMessage (buffer) = Error Type: @Value(errorType)
        FME Rejection Code: @Value(fme_rejection_code)

        Notify FME Specialist
    -> Junction_54
Junction_54
    -> Junction_24
Note: Format Attributes for Excel Report
AttributeManager_5
    ATTR_TABLE:
      RENAME_SET_VALUE transects_SA2_Number > SA2_Number (real64)
      RENAME_SET_VALUE transects_SA_Name > SA_Name (varchar(256))
      RENAME_SET_VALUE sa2_Required_Transects_MPI > Required_Transects_MPI (uint8)
      RENAME_SET_VALUE sa2_New_Transects_MPI > New_Transects_MPI (varchar(200))
      RENAME_SET_VALUE sa2_Exiting_Selected_Transects > Exiting_Selected_Transects (real64)
      RENAME_SET_VALUE transects_transect_id > Transect_ID (int32)
      RENAME_SET_VALUE transects_transect_comments > Transect_Comments (varchar(1000))
      RENAME_SET_VALUE transects_inspection_date > Transect_Previous_Inspection_Date (int64)
      RENAME_SET_VALUE vegetation_host_identity > Veg_Host_Identity (varchar(255))
      RENAME_SET_VALUE vegetation_confirmed_presence > Veg_Confirmed_Presence (varchar(255))
      RENAME_SET_VALUE vegetation_Priority > Veg_Priority (varchar(255))
      RENAME_SET_VALUE _order_priority_transect > Veg_Count_In_Transect (int64)
      REMOVE Scheduled_for_Round (varchar(200))
      REMOVE scheduled_for_round1 (varchar(200))
      REMOVE scheduled_for_round2 (varchar(200))
      REMOVE scheduled_for_round3 (varchar(200))
      REMOVE transects_HRSS-Spreadsheet (varchar(200))
      REMOVE transects_AGOL_SA2_2023_HRSS_Locus (varchar(200))
      REMOVE sa2_OBJECTID (int32)
      REMOVE sa2_SA22023_V1 (varchar(6))
      REMOVE transects_objectid (int32)
      REMOVE transects_globalid (varchar(38))
      REMOVE transects_created_user (varchar(255))
      REMOVE transects_created_date (int64)
      REMOVE transects_last_edited_user (varchar(255))
      REMOVE transects_last_edited_date (int64)
      REMOVE transects_scheduled_for_round1 (varchar(255))
      REMOVE transects_scheduled_for_round2 (varchar(255))
      REMOVE transects_scheduled_for_round3 (varchar(255))
      REMOVE transects_transect_status (varchar(255))
      REMOVE transects_rsa_abbreviation (varchar(255))
      REMOVE transects_traffic_details (varchar(255))
      REMOVE transects_personal_security (varchar(255))
      REMOVE transects_safety_comments (varchar(1000))
      REMOVE transects_surveyorid (int32)
      REMOVE transects_inspection_status (varchar(255))
      REMOVE transects_inspection_stage (varchar(255))
      REMOVE transects_tvd_quality (int16)
      REMOVE transects_Round_1_Date (int64)
      REMOVE transects_Round_2_Date (int64)
      REMOVE transects_Round_3_Date (int64)
      REMOVE transects_R1_Inspection_Status (varchar(256))
      REMOVE transects_R2_Inspection_Status (varchar(256))
      REMOVE transects_R3_Inspection_status (varchar(256))
      REMOVE transects_Host_Count (int16)
      REMOVE transects_Crosby (varchar(255))
      REMOVE transects_Scheduled_for_Round (varchar(255))
      REMOVE transects_Shape__Length (real64)
      REMOVE vegetation_objectid (int32)
      REMOVE vegetation_globalid (varchar(38))
      REMOVE vegetation_created_user (varchar(255))
      REMOVE vegetation_created_date (int64)
      REMOVE vegetation_last_edited_user (varchar(255))
      REMOVE vegetation_last_edited_date (int64)
      REMOVE vegetation_parentid (varchar(38))
      REMOVE sa2_SA22023_V1.total_count (uint64)
      REMOVE vegetation_Priority_Number (buffer)
      REMOVE sa2_HRSS_Transects_to_Schedule (int32)
      REMOVE sa2_New_Transects_Active_to_Validate_HRSS (real64)
      REMOVE sa2_Required_Transects_Active_to_Validate_HRSS (real64)
    USER_EXPOSED_ATTRIBUTES = sa2_SA2_Transect_Selection_Completed
    -> Sorter_4
Note: Sort by SA2_Number
Sorter_4
    SORT_PARM = SA2_Number NUMERIC ASCENDING Veg_Count_In_Transect NUMERIC ASCENDING
    SORTED -> _FINAL
    SORTED -> FeatureWriter_4 [Sorted]
_FINAL: Inspector [off]
Note: FAILED VALIDATION
Junction_26
    -> Junction_27
Note: Error
Junction_19
    -> Junction_20
Junction_23
    -> FeatureWriter_4 [Sorted00]
Note: Error
AttributeCreator_20
    ATTR_TABLE:
      SET_TO errorType (buffer) = FeatureMerger_4 - Merging Vegetation to Transects
      SET_TO errorMessage (buffer) = Error Type: @Value(errorType)
        FME Rejection Code: @Value(fme_rejection_code)

        Notify FME Specialist
    -> Junction_18
Note: Error
AttributeCreator_32
    ATTR_TABLE:
      SET_TO errorType (buffer) = FeatureMerger_3 - Error merging Transects to SA2_Number
      SET_TO errorMessage (buffer) = FME Rejection Code: @Value(fme_rejection_code)

        Verify no duplicate SA2_Numbers exist in AGOL Layers, then notify FME Specialist
    -> Junction_49
Note: SA2 - No Transects
Junction_3
    -> StatisticsCalculator_4
Note: Summary Info
Junction_34
    -> AttributeManager_9
Note: REPORT Summary Numbers
AttributeManager_9
    ATTR_TABLE:
      RENAME_SET_VALUE sa2_HRSS_Transects_to_Schedule > HRSS_Transects_to_Schedule (int32)
      RENAME_SET_VALUE sa2_Required_Transects_Active_to_Validate_HRSS > Required_Transects_SA2_Active (real64)
      RENAME_SET_VALUE sa2_New_Transects_Active_to_Validate_HRSS > New_Transects_SA2_Active (real64)
      RENAME_SET_VALUE sa2_HRSS_Transects_to_Schedule.total_count > HRSS_Transects_Scheduled (uint64)
      RENAME_SET_VALUE sa2_Required_Transects_NoTransects_to_Validate_HRSS > Required_Transects_NoTransects_Available (real64)
      RENAME_SET_VALUE sa2_New_Transects_NoTransects_to_Validate_HRSS > New_Transects_NoTransects_Available (real64)
      RENAME_SET_VALUE sa2_HRSS_Transects_to_Schedule-AUTOMATED > HRSS_Transects_to_Schedule-MANUAL (uint64)
      SET_TO All_Transects_Required (real64) = @Evaluate(@Value(New_Transects_SA2_Active)+@Value(HRSS_Transects_Scheduled)+@Value(Required_Transects_NoTransects_Available)+@Value(HRSS_Transects_to_Schedule-MANUAL))
      SET_TO Transects_Available_PLUS_Req_New_Transects (real64) = @Evaluate(@Value(Required_Transects_SA2_Active)+@Value(New_Transects_NoTransects_Available))
    -> Junction_36
    -> AttributeKeeper_5
Junction_36
    -> FeatureWriter_4 [Sheet1]
Note: Trigger for Final Write
FeatureMerger_10
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> FeatureWriter_3 [UnmergedRequestor]
    MERGED -> _Transect_2425_Layer
    <REJECTED> -> AttributeCreator_25
_Transect_2425_Layer: Inspector [off]
Note: Update Transect Layer / Scheduled_for_Round scheduled_for_round1, 2, 3
Note: UPDATE SPS BIOTA AGOL
FeatureWriter_3
    DATASET_ATTR = _dataset
    FEATURE_TYPE_LIST_ATTR = _feature_types
    FORMAT = SAFE.ESRI-AGOL.ARCGISFEATURESERVICE
    SAFE.ESRI-AGOL.ARCGISFEATURESERVICE_AGOL_AUTH_NC = $(AGOL_USER_AUTHORIZATION)
    SAFE.ESRI-AGOL.ARCGISFEATURESERVICE_ALWAYS_CREATE_FEATURE_TYPES = NO
    SAFE.ESRI-AGOL.ARCGISFEATURESERVICE_APPEND_FORMAT = geojson
    SAFE.ESRI-AGOL.ARCGISFEATURESERVICE_ASYNC_WRITE = NO
    SAFE.ESRI-AGOL.ARCGISFEATURESERVICE_FEATURES_PER_REQUEST = 1000
    SAFE.ESRI-AGOL.ARCGISFEATURESERVICE_FEATURE_SERVICE_HANDLING = USE_EXISTING
    SAFE.ESRI-AGOL.ARCGISFEATURESERVICE_FEATURE_SERVICE_WITH_ID = Transects_HRSS_Staging_2425_(84be2ae7b5494766bb0bc390aa4111e6)
    SAFE.ESRI-AGOL.ARCGISFEATURESERVICE_GROUP_ID = 02af8fa42acc4054a20f72f705d115db
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_GLOBAL_ID = NO
    SAFE.ESRI-AGOL.ARCGISFEATURESERVICE_VERIFY_HTTPS = WEB_CONN
    TOTAL_FEATURES_WRITTEN_ATTR = _total_features_written
Note: Error
AttributeCreator_25
    ATTR_TABLE:
      SET_TO errorType (buffer) = FeatureMerger_10 - Trigger Final Write
      SET_TO errorMessage (buffer) = Error Type: @Value(errorType)
        FME Rejection Code: @Value(fme_rejection_code)

        Notify FME Specialist
    -> Junction_25
Note: FAILED VALIDATION
Junction_27
    -> Junction_30
Note: Error
Junction_20
    -> Junction_35
Junction_35
    -> Junction_21
Note: Error
Junction_21
    -> Junction_22
Note: Format Attributes for Excel Report
AttributeManager_6
    ATTR_TABLE:
      RENAME_SET_VALUE sa2_SA22023_V1 > SA2_Number (varchar(6))
      RENAME_SET_VALUE sa2_Required_Transects_MPI > Required_Transects_MPI (uint8)
      RENAME_SET_VALUE sa2_New_Transects_MPI > New_Transects_MPI (varchar(200))
      RENAME_SET_VALUE sa2_Exiting_Selected_Transects > Exiting_Selected_Transects (real64)
      REMOVE sa2_OBJECTID (int32)
      REMOVE sa2_HRSS_Transects_to_Schedule (int32)
      REMOVE sa2_Required_Transects_MPI.sum (real64)
      REMOVE sa2_New_Transects_MPI.sum (real64)
    USER_EXPOSED_ATTRIBUTES = sa2_Required_Transects.sum,sa2_New_Transects.sum,sa2_SA2_Transect_Selection_Completed
    -> Sorter_5
Note: Sort by SA2_Number
Sorter_5
    SORT_PARM = SA2_Number NATURAL ASCENDING
    SORTED -> Junction_2
Junction_2
    -> FeatureWriter_4 [Output]
Note: FINAL REPORT - Excel
Note: UPDATE SPS BIOTA NETWORK
FeatureWriter_4
    DATASET = $(OUTPUT_FOLDER)/MPI-HRSS_Report_@DateTimeFormat(@DateTimeNow(local),%Y%m%d).xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
Note: Error
AttributeCreator_19
    ATTR_TABLE:
      SET_TO errorType (buffer) = FeatureMerger_2 - Opening the Gate, if no Errors
      SET_TO errorMessage (buffer) = Error: @Value(errorType)
        FME Rejection Code: @Value(fme_rejection_code)

        Notify FME Specialist
    -> Junction_15
Note: Error
AttributeCreator_2
    ATTR_TABLE:
      SET_TO errorType (buffer) = FeatureReader_5 - AGOL MPI HRSS Transects Table
      SET_TO errorMessage (buffer) = Error Type: @Value(errorType)
        Reader Error: @Value(_reader_error)
        Rejection Code: @Value(fme_rejection_code)

        Verify SPS Biota MPI HRSS Table is valid, then contact FME Specialist.
    -> Junction_38
Note: Error
AttributeCreator_33
    ATTR_TABLE:
      SET_TO errorType (buffer) = FeatureMerger_15 - Error Merging HRSS MPI Transects to AGOL MPI HRSS Transects Table on SA2 Code
      SET_TO errorMessage (buffer) = Error Type: @Value(errorType)
        Rejection Code: @Value(fme_rejection_code)

        Verify MPI HRSS Input Spreadsheet does not contain Duplicates, then contact FME Specialist.
    -> Junction_6
Note: Error
AttributeCreator_35
    ATTR_TABLE:
      SET_TO errorType (buffer) = FeatureReader_7 - AGOL MPI HRSS Transects Table
      SET_TO errorMessage (buffer) = Error Type: @Value(errorType)
        Reader Error: @Value(_reader_error)
        Rejection Code: @Value(fme_rejection_code)

        Verify SPS Biota MPI HRSS Table (in AGOL) is valid, then contact FME Specialist.
    -> Junction_48

Bookmark: Backup MPI HRSS Spreadsheet to AGOL
Note: Upload MPI HRSS Backup
ArcGISOnlineConnector_2
    OPERATION_TYPE = Upload
    PARAMETER_SETUP = _FME_SOURCE_TYPE]File]_FME_SOURCE_FILE]$(excel_mpi_hrss_spreadsheet)]_FME_DATA_TO_UPLOAD]<Unused>]_FME_URL_UPLOAD]<Unused>]_UPLOAD_FILE_TITLE]HRSS SA2 Target Table_$(INSPECTION_SEASON)_Rnd$(INSPECTION_ROUND)]FILE_ITEM_TYPE]Use File Extension]_URL_ITEM_TYPE]<Unused>]_UPLOAD_FILE_TAGS]MPI,HRSS]_FME_UPLOAD_DESTINATION_PATH][{"display":"/Gavin Scratch","value":"a61ee8f2c29947299e6de928ec6f16e2"}]]_FME_UPLOAD_ATTR_FILENAME]<Unused>]_UPLOAD_FME_ATTRIBUTES_TO_ADD]"_id _private_url"]FME_CONTROLLER_QUERY_FILE]esri_agol_deps/Upload.fme]FME_CONTROLLER_CHOICE]Upload
    __arcgisonlineconnector_connection = $(AGOL_USER_AUTHORIZATION)
    -> AttributeKeeper_9
    <Rejected> -> ArcGISOnlineConnector_3
Note: Delete Pre-existing upload
ArcGISOnlineConnector_3
    OPERATION_TYPE = Delete
    PARAMETER_SETUP = _FME_FILEID]@Value(_conflicting_id)]PERMANENT_DELETE]YES]_DELETE_FME_ATTRIBUTES_TO_ADD]"_success _id"]FME_CONTROLLER_QUERY_FILE]esri_agol_deps/Delete.fme]FME_CONTROLLER_CHOICE]Delete
    __arcgisonlineconnector_connection = $(AGOL_USER_AUTHORIZATION)
    -> ArcGISOnlineConnector_5
    <Rejected> -> AttributeCreator_30
Note: Upload MPI HRSS Backup
ArcGISOnlineConnector_5
    OPERATION_TYPE = Upload
    PARAMETER_SETUP = _FME_SOURCE_TYPE]File]_FME_SOURCE_FILE]$(excel_mpi_hrss_spreadsheet)]_FME_DATA_TO_UPLOAD]<Unused>]_FME_URL_UPLOAD]<Unused>]_UPLOAD_FILE_TITLE]HRSS SA2 Target Table_$(INSPECTION_SEASON)_Rnd$(INSPECTION_ROUND)]FILE_ITEM_TYPE]Use File Extension]_URL_ITEM_TYPE]<Unused>]_UPLOAD_FILE_TAGS]MPI,HRSS]_FME_UPLOAD_DESTINATION_PATH][{"display":"/Gavin Scratch","value":"a61ee8f2c29947299e6de928ec6f16e2"}]]_FME_UPLOAD_ATTR_FILENAME]<Unused>]_UPLOAD_FME_ATTRIBUTES_TO_ADD]"_id _private_url"]FME_CONTROLLER_QUERY_FILE]esri_agol_deps/Upload.fme]FME_CONTROLLER_CHOICE]Upload
    __arcgisonlineconnector_connection = $(AGOL_USER_AUTHORIZATION)
    -> AttributeKeeper_9
    <Rejected> -> AttributeCreator_30
AttributeKeeper_9
    CREATE_BULK_MODE_FEATURES = NO
    -> FeatureMerger_16 [SUPPLIER]
    -> FeatureMerger_17 [SUPPLIER]
Note: Error
AttributeCreator_30
    ATTR_TABLE:
      SET_TO errorType (buffer) = ArcGISOnlineConnector - Backup MPI HRSS Spreadsheet to AGOL
      SET_TO errorMessage (buffer) = There was an error when uploading the MPI HRSS Spreadsheet to AGOL.

        Error Type: @Value(errorType)
        Rejection Message: @Value(fme_rejection_message)
    -> Junction_47

Bookmark: Open the Gate for all MPI HRSS Spreadsheet data to Pass
FeatureMerger_16
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> FeatureMerger_13 [SUPPLIER]
    <REJECTED> -> Junction_33
FeatureMerger_17
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> FeatureMerger_14 [SUPPLIER]
    <REJECTED> -> Junction_33
Note: Error
Junction_33
    -> AttributeCreator_34
Junction_39
    -> FeatureMerger_13 [REQUESTOR]
    -> FeatureMerger_14 [REQUESTOR]
FeatureMerger_13
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> AttributeExposer
    <REJECTED> -> AttributeCreator_34
FeatureMerger_14
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> AttributeExposer_3
    <REJECTED> -> AttributeCreator_34
Note: Error
AttributeCreator_34
    ATTR_TABLE:
      SET_TO errorType (buffer) = Bookmark: "Open the Gate for all MPI HRSS Spreadsheet data to Pass" - Error passing data through Gate
      SET_TO errorMessage (buffer) = Error Type: @Value(errorType)
        Rejection Code: @Value(fme_rejection_code)

        Verify MPI HRSS Input Spreadsheet, then contact FME Specialist.
    -> Junction_43

Bookmark: Validate Spreadsheet
ParameterFetcher_2
    ATTR_LIST = _excel_mpi_hrss_sheetname $(excel_mpi_hrss_sheetname)
    -> TestFilter_11
TestFilter_11
    DEFAULT_VALUE = <UNFILTERED>
    PASSED_TEST_GROUP_OUTPUT = FIRST
    TEST_LIST = "BOOL_OP,OR,COMPOSITE_TEST,""""""1"""""",TEST_CLAUSE,TEST @Value(fme_feature_type) = @Value(_excel_mpi_hrss_sheetname)",PASS-Sheet,"BOOL_OP,OR,COMPOSITE_TEST,""""""1"""""",TEST_CLAUSE,CASE_INSENSITIVE_TEST _excel_mpi_hrss_sheetname ATTRIBUTE_HAS_A_VALUE """,NotApplicable
    PASS-Sheet -> NoFeaturesTester_2
    <UNFILTERED> -> AttributeCreator_27
NoFeaturesTester_2
    NoInput -> AttributeCreator_27
    -> Junction_39
Note: Error
AttributeCreator_27
    ATTR_TABLE:
      SET_TO errorType (buffer) = TestFilter_11 - MPI HRSS Sheet Name
      SET_TO errorMessage (buffer) = Input Spreadsheet Validation FAILED

        Verify the input spreadsheet schema matches:
        - SA2_2023 Code
        - SA2_2023 Name
        - Transects

        Verify each spreadsheet row and column has data. For example:
        SA2_2023 Code | SA2_2023 Name | Transects
        100100 | North Cape | 0
    -> Junction_42

Bookmark: ERROR
Junction_41
    -> Junction_42
Junction_42
    -> Junction_46
Junction_46
    -> Junction_47
Junction_47
    -> Junction_43
Junction_43
    -> Junction_48
Junction_48
    -> Junction_44
Junction_44
    -> Junction_6
Junction_6
    -> Junction_38
Junction_38
    -> Junction_10
Junction_10
    -> Junction_11
Junction_11
    -> Junction_12
Junction_12
    -> Junction_14
Junction_14
    -> Junction_15
Junction_15
    -> Junction_16
Junction_16
    -> Junction_49
Junction_49
    -> Junction_50
Junction_50
    -> Junction_17
Junction_17
    -> Junction_18
Junction_18
    -> Junction_30
Junction_30
    -> Junction_22
Junction_22
    -> Junction_31
Junction_31
    -> Junction_24
Junction_24
    -> Junction_25
Junction_25
    -> Terminator
Terminator
    MESSAGE:
      ****************************

      Translation Terminated

      Error Type:
      @Value(errorType)

      Error Message:
      @Value(errorMessage)


      *****************************

Bookmark: Validation Attribute
Note: Sum Transects to Schedule
StatisticsCalculator_2
    ATTR_ACCUM_MODE = None
    CALCULATION_MODE = NUMERIC
    FEAT_STATS = Transects,NUMERIC_MODE,,,,SUM,,,,,,,,,
    COMPLETE -> AttributeManager_4
Note: HRSS_Transects_to_Schedule
AttributeManager_4
    ATTR_TABLE = RENAME_SET_VALUE Transects.sum > HRSS_Transects_to_Schedule (int32)
    -> Sampler

Bookmark: Refresh Staging Table with Production Data
Note: PRODUCTION / SPS Biota AGOL - SA2_2023 Data
FeatureReader_3
    ATTRIBUTES = SA2_2023_HRSS_Locus,"OBJECTID,SA22023_V1,SA22023__1,SA22023__2,Active,LAND_AREA_,AREA_SQ_KM,Shape_Leng,Count_Transects,Field,Required_Transects,New_Transects,SA2_Comments,SA2_Abbrev,Status,Crosby,Who,Crosby_Code,Tota_Transects,SA2_Transects_Completed,Contain_Transects,SA2_Number,GlobalID,Shape__Area,Shape__Length,Selection_Status"
    ATTR_ACCUM_MODE = Only Use Result
    CLIP_TO_ENVELOPE = NO
    COMBINE_GEOM = Use Result
    FEATURETYPES = SA2_2023_HRSS_Locus
    FORMAT = SAFE.ESRI-AGOL.ARCGISFEATURESERVICE
    GEOMETRY_TYPES = SA2_2023_HRSS_Locus,""",fme_area"""
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = $(AGOL_USER_AUTHORIZATION)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = SA2_2023_HRSS_Locus(a96480b1f8e24821a7acceb6d3a4f642)
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_GROUP_ID = 02af8fa42acc4054a20f72f705d115db
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    SA2_2023_HRSS_Locus -> HTTPCaller
    <REJECTED> -> AttributeCreator_5
Note: Overwrite STAGING AGOL layer
FeatureWriter_6
    DATASET_ATTR = _dataset
    FEATURE_TYPE_LIST_ATTR = _feature_types
    FORMAT = SAFE.ESRI-AGOL.ARCGISFEATURESERVICE
    SAFE.ESRI-AGOL.ARCGISFEATURESERVICE_AGOL_AUTH_NC = Locus Esri ArcGIS Online OAuth (safe.esri-agol)
    SAFE.ESRI-AGOL.ARCGISFEATURESERVICE_ALWAYS_CREATE_FEATURE_TYPES = NO
    SAFE.ESRI-AGOL.ARCGISFEATURESERVICE_APPEND_FORMAT = geojson
    SAFE.ESRI-AGOL.ARCGISFEATURESERVICE_ASYNC_WRITE = YES
    SAFE.ESRI-AGOL.ARCGISFEATURESERVICE_ASYNC_WRITE_TIMEOUT = 1200
    SAFE.ESRI-AGOL.ARCGISFEATURESERVICE_ASYNC_WRITE_WAIT = YES
    SAFE.ESRI-AGOL.ARCGISFEATURESERVICE_FEATURES_PER_REQUEST = 50
    SAFE.ESRI-AGOL.ARCGISFEATURESERVICE_FEATURE_SERVICE_HANDLING = USE_EXISTING
    SAFE.ESRI-AGOL.ARCGISFEATURESERVICE_FEATURE_SERVICE_WITH_ID = SA2 2023 HRSS Staging(615650d4be7a47189a304aeef94cbebc)
    SAFE.ESRI-AGOL.ARCGISFEATURESERVICE_GROUP_ID = 02af8fa42acc4054a20f72f705d115db
    SAFE.ESRI-AGOL.ARCGISFEATURESERVICE_PRESERVE_GLOBALID = NO
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_GLOBAL_ID = YES
    SAFE.ESRI-AGOL.ARCGISFEATURESERVICE_VERIFY_HTTPS = WEB_CONN
    TOTAL_FEATURES_WRITTEN_ATTR = _total_features_written
    SUMMARY -> FeatureReader_6 [INITIATOR]
Note: Error
AttributeCreator_5
    ATTR_TABLE:
      SET_TO errorType (buffer) = FeatureReader - SPS Biota AGOL SA2_2023
      SET_TO errorMessage (buffer) = Reader Error: @Value(_reader_error)
        FME Rejection Code: @Value(fme_rejection_code)

        Notify FME Specialist
    -> Junction_9
Junction_9
    -> Junction_8
Junction_8
    -> Junction_10

Bookmark: GET Count_Transects - from Transects Layer
Note: UPDATE WITH PRODUCTION TRANSECTS TABLE
Note: WHERE transect_status = 'Active' AND SA2_Number = ######, Return Count
Note: https://services7.arcgis.com/LC2ZYuzjoMc34UJK/ArcGIS/rest/services/HRSS_Locus_Transects_2425/FeatureServer/0/query?where=transect_status+=+'Active'+AND+SA2_Number+=+@Value(SA22023_V1)&returnCountOnly=true&f=json
HTTPCaller
    AUTH_METHOD_TYPE = NC
    AUTH_NAMED_CONNECTION = $(AGOL_USER_AUTHORIZATION)
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://services7.arcgis.com/LC2ZYuzjoMc34UJK/arcgis/rest/services/Transects_HRSS_Staging_2425_/FeatureServer/0/query?where=transect_status+=+'Active'+AND+SA2_Number+=+@Value(SA22023_V1)&returnCountOnly=true&f=json
    TRANSFER_TIMEOUT_LENGTH = 90
    USE_COOKIES = No
    VERIFY_SSL_CERTIFICATES = Yes
    AUTH_METHOD = Web Connection
    -> JSONExtractor
    <REJECTED> -> AttributeCreator_17
Note: Parse JSON "count"
JSONExtractor
    EXTRACT_QUERY_TABLE = Count_Transects json["count"]
    JSON_DOCUMENT = @Value(_response_body)
    READ_FROM_FILE = NO
    EVALUATED -> AttributeManager_10
    <REJECTED> -> AttributeCreator_17
Note: Set Contain_Transects / Remove HTML Attr's
AttributeManager_10
    ATTR_TABLE:
      SET_TO Contain_Transects (varchar(255)) = FME_CONDITIONAL:DEFAULT_VALUE'No'BOOL_OP;OR;COMPOSITE_TEST;1;TEST @Value(Count_Transects) > 0'Yes'FME_NUM_CONDITIONS2___
      RENAME_SET_VALUE Required_Transects > Required_Transects_MPI (int32)
      RENAME_SET_VALUE New_Transects > New_Transects_MPI (int32)
      RENAME_SET_VALUE Tota_Transects > Exiting_Selected_Transects (int32)
      RENAME_SET_VALUE Status > SA2_Inspection_Status_SPS (varchar(255))
      RENAME_SET_VALUE Active > Active_SA2_MPI (varchar(254))
      RENAME_SET_VALUE GlobalID > globalid (varchar(38))
      RENAME_SET_VALUE Selection_Status > SA2_Transect_Selection_Completed (varchar(255))
      REMOVE LAND_AREA_ (real64)
      REMOVE AREA_SQ_KM (real64)
      REMOVE Shape_Leng (real64)
      REMOVE Field (int32)
      REMOVE SA2_Abbrev (varchar(255))
      REMOVE SA2_Transects_Completed (varchar(256))
      REMOVE _response_body (buffer)
      REMOVE _http_status_code (buffer)
    USER_EXPOSED_ATTRIBUTES = Active_SA2_MPI,Contain_Transects,Count_Transects,Crosby,Crosby_Code,Exiting_Selected_Transects,globalid,New_Transects_MPI,OBJECTID,Required_Transects_MPI,SA2_Comments,SA2_Inspection_Status_SPS,SA2_Number,SA2_Transect_Selection_Completed,SA22023__1,SA22023__2,SA22023_V1,Shape__Area,Shape__Length,Who
    -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> FeatureWriter_6 [SA2_2023_HRSS_Locus]
    <REJECTED> -> AttributeCreator_17
Note: Error
AttributeCreator_17
    ATTR_TABLE:
      SET_TO errorType (buffer) = Bookmark: GET Count_Transects - HTTPCaller or JSONExtractor
      SET_TO errorMessage (buffer) = Error Fetching HTTP / JSON

        Error Type: @Value(errorType)
        Error: @Value(_error)
        Status Code: @Value(_http_status_code)
        Rejection Code: @Value(fme_rejection_code)
    -> Junction_7
Junction_7
    -> Junction_8

Bookmark: Extra HRSS Data in MPI Spreadsheet
TestFilter_2
    DEFAULT_VALUE = <UNFILTERED>
    PASSED_TEST_GROUP_OUTPUT = FIRST
    TEST_LIST = "BOOL_OP,OR,COMPOSITE_TEST,""""""1"""""",TEST_CLAUSE,TEST @Value(Transects) = 0",Warning,"BOOL_OP,OR,COMPOSITE_TEST,""""""1"""""",TEST_CLAUSE,TEST @Value(Transects) > 0",Error
    Warning -> AttributeCreator_6
    Error -> Sampler_2
    <UNFILTERED> -> AttributeCreator_6
Note: Warning
AttributeCreator_6
    ATTR_TABLE:
      SET_TO warningType (buffer) = TestFilter_2 - Merging HRSS Spreadsheet to SPS AGOL SA2_2023_HRSS data
      SET_TO warningMessage (varchar(200)) = This SA2 (@Value(SA2_2023 Code), @Value(SA2_2023 Name)) exists in HRSS Spreadsheet from MPI, however it is not in SPS Biota AGOL SA2_2023 table. - ZERO Transects to Review. Warning only.
    -> Junction_28
Note: Warning
Junction_28
    -> Junction_29
Sampler_2
    MODE = ORIGINAL
    RATE = 1
    SAMPLE_TYPE_MULTIPLIER = 0
    SAMPLE_MODE = No
    SAMPLE_TYPE_LONG = Last N Features
    SAMPLED -> AttributeCreator_4
    SAMPLED -> FeatureMerger_2 [SUPPLIER]
    NOT_SAMPLED -> AttributeCreator_4
Note: Error
AttributeCreator_4
    ATTR_TABLE:
      SET_TO errorType (buffer) = TestFilter_2 - Merging HRSS Spreadsheet to SPS AGOL SA2_2023_HRSS data
      SET_TO errorMessage (varchar(200)) = This SA2 (@Value(SA2_2023 Code), @Value(SA2_2023 Name)) exists in HRSS Spreadsheet from MPI, however it is not in SPS Biota AGOL SA2_2023 table. - @Value(Transects) Transects to Review.

        ERROR - Translation Terminated
    -> Junction_14

Bookmark: Read-in Transect Data, all attributes set with transects_
Note: Transect Feature Service / Verify when deploying to SPS Biota Environment
FeatureReader
    ATTRIBUTES = Transects_2425_,"objectid,globalid,created_user,created_date,last_edited_user,last_edited_date,transect_id,transect_comments,scheduled_for_round1,scheduled_for_round2,scheduled_for_round3,transect_status,rsa_abbreviation,traffic_details,personal_security,safety_comments,inspection_date,surveyorid,inspection_status,inspection_stage,tvd_quality,Round_1_Date,Round_2_Date,Round_3_Date,R1_Inspection_Status,R2_Inspection_Status,R3_Inspection_status,Host_Count,SA2_Number,SA_Name,Crosby,Scheduled_for_Round,Shape__Length",Vegetation,"objectid,globalid,created_user,created_date,last_edited_user,last_edited_date,parentid,host_identity,confirmed_presence,Priority"
    ATTR_ACCUM_MODE = Only Use Result
    CLIP_TO_ENVELOPE = NO
    COMBINE_GEOM = Use Result
    FEATURETYPES = Transects_2425_
    FORMAT = SAFE.ESRI-AGOL.ARCGISFEATURESERVICE
    GEOMETRY_TYPES = Transects_2425_,""",fme_line"""
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = $(AGOL_USER_AUTHORIZATION)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = Transects_HRSS_Staging_2425_(84be2ae7b5494766bb0bc390aa4111e6)
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_GROUP_ID = 02af8fa42acc4054a20f72f705d115db
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    Transects_2425_ -> BulkAttributeRenamer
    Transects_2425_ -> Junction_4
    <REJECTED> -> AttributeCreator_3
Note: Prefix with transects_
BulkAttributeRenamer
    ATTRCHOICE_ACTION = SELECTED
    ATTRLIST = created_date created_user Crosby globalid Host_Count inspection_date inspection_stage inspection_status last_edited_date last_edited_user objectid personal_security R1_Inspection_Status R2_Inspection_Status R3_Inspection_status Round_1_Date Round_2_Date Round_3_Date rsa_abbreviation SA_Name SA2_Number safety_comments Scheduled_for_Round scheduled_for_round1 scheduled_for_round2 scheduled_for_round3 Shape__Length surveyorid traffic_details transect_comments transect_id transect_status tvd_quality
    MODE_CHOICE = RENAME
    PATTERN_ACTION_DISP = ADDPREFIX
    REPLACE_STR = transects_
    ATTRCHOICE = Selected Attributes
    -> TestFilter_6
TestFilter_6
    DEFAULT_VALUE = <UNFILTERED>
    PASSED_TEST_GROUP_OUTPUT = FIRST
    TEST_LIST = "BOOL_OP,OR,COMPOSITE_TEST,""""""1"""""",TEST_CLAUSE,TEST @Value(transects_transect_status) = Active",Active
    Active -> AttributeCreator_11
Note: Error
AttributeCreator_3
    ATTR_TABLE:
      SET_TO errorType (buffer) = FeatureReader - Transect Selection from AGOL
      SET_TO errorMessage (buffer) = Reader Error: @Value(_reader_error)
        FME Rejection Code: @Value(fme_rejection_code)

        Notify FME Specialist
    -> Junction_16

Bookmark: parent_id
Note: Create parent_id for merge
AttributeCreator_11
    ATTR_TABLE = SET_TO vegetation_parentid (varchar(200)) = {@Value(transects_globalid)}
    -> StringCaseChanger
StringCaseChanger
    ATTRCHOICE = SELECTED
    ATTRLIST = vegetation_parentid
    CHANGE_TYPE = upper
    -> FeatureMerger_3 [REQUESTOR]

Bookmark: Validation Calculations
Note: Filter one SA2 Feature
Sampler_6
    GROUP_BY = sa2_SA22023_V1
    MODE = ORIGINAL
    RATE = 1
    SAMPLE_TYPE_MULTIPLIER = -1
    SAMPLE_MODE = No
    SAMPLE_TYPE_LONG = First N Features
    SAMPLED -> StatisticsCalculator_5
    SAMPLED -> FeatureMerger_5 [REQUESTOR]
    NOT_SAMPLED -> FeatureMerger_5 [REQUESTOR]
Note: Sum Req and New Transects
StatisticsCalculator_5
    ATTR_ACCUM_MODE = None
    CALCULATION_MODE = NUMERIC
    FEAT_STATS = sa2_Required_Transects_MPI,NUMERIC_MODE,,,,SUM,,,,,,,,,;sa2_New_Transects_MPI,NUMERIC_MODE,,,,SUM,,,,,,,,,
    SUMMARY -> AttributeRenamer
Note: Rename to logical attributes
AttributeRenamer
    ATTR_TABLE:
      RENAME_SET_DEFAULT sa2_New_Transects_MPI.sum > sa2_New_Transects_Active_to_Validate_HRSS
      RENAME_SET_DEFAULT sa2_Required_Transects_MPI.sum > sa2_Required_Transects_Active_to_Validate_HRSS
    KEEP_RENAMED_ONLY = no
    MISSING_INPUT_ATTRS = REMOVE
    -> FeatureMerger_5 [SUPPLIER]
Note: Merge Req, New Counts
FeatureMerger_5
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> FeatureMerger_4 [SUPPLIER]
    MERGED -> Sampler_3
    <REJECTED> -> AttributeCreator_36
Note: Error
AttributeCreator_36
    ATTR_TABLE:
      SET_TO errorType (buffer) = FeatureMerger_5 - Error merging trigger to SA2 Features
      SET_TO errorMessage (buffer) = FME Rejection Code: @Value(fme_rejection_code)

        Notify FME Specialist
    -> Junction_50

Bookmark: Read-in Vegetation Data, all attributes set with vegetation_
Note: Vegetation Feature Service / Verify when deploying to SPS Biota Environment
FeatureReader_4
    ATTRIBUTES = Transects_2425_,"objectid,globalid,created_user,created_date,last_edited_user,last_edited_date,transect_id,transect_comments,scheduled_for_round1,scheduled_for_round2,scheduled_for_round3,transect_status,rsa_abbreviation,traffic_details,personal_security,safety_comments,inspection_date,surveyorid,inspection_status,inspection_stage,tvd_quality,Round_1_Date,Round_2_Date,Round_3_Date,R1_Inspection_Status,R2_Inspection_Status,R3_Inspection_status,Host_Count,SA2_Number,SA_Name,Crosby,Scheduled_for_Round,Shape__Length",Vegetation,"objectid,globalid,created_user,created_date,last_edited_user,last_edited_date,parentid,host_identity,confirmed_presence,Priority"
    ATTR_ACCUM_MODE = Only Use Result
    CLIP_TO_ENVELOPE = NO
    COMBINE_GEOM = Use Result
    FEATURETYPES = Vegetation
    FORMAT = SAFE.ESRI-AGOL.ARCGISFEATURESERVICE
    GEOMETRY_TYPES = Transects_2425_,""",fme_line"""
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = $(AGOL_USER_AUTHORIZATION)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 5000
    SAFE.ESRI-AGOL.ARCGISFEATURESERVICE_FEATURE_SERVICE_WITH_ID = Transects_HRSS_Staging_2425_(84be2ae7b5494766bb0bc390aa4111e6)
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_GROUP_ID = 02af8fa42acc4054a20f72f705d115db
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    Vegetation -> BulkAttributeRenamer_2
    <REJECTED> -> AttributeCreator_8
Note: Prefix with vegetation_
BulkAttributeRenamer_2
    ATTRCHOICE_ACTION = SELECTED
    ATTRLIST = confirmed_presence created_date created_user globalid host_identity last_edited_date last_edited_user objectid parentid Priority
    MODE_CHOICE = RENAME
    PATTERN_ACTION_DISP = ADDPREFIX
    REPLACE_STR = vegetation_
    ATTRCHOICE = Selected Attributes
    -> FeatureMerger_4 [REQUESTOR]
Note: Error
AttributeCreator_8
    ATTR_TABLE:
      SET_TO errorType (buffer) = FeatureReader_4 - Vegetation Selection from AGOL
      SET_TO errorMessage (buffer) = Reader Error: @Value(_reader_error)
        FME Rejection Code: @Value(fme_rejection_code)

        Notify FME Specialist
    -> Junction_17

Bookmark: POTENTIAL PRIORITY METHOD: COUNT NUMBER OF VEG IN TRANSECT BY PRIORITY VALUE
Aggregator_2 [off]
    ACCUM_ATTRS_NAME = Drop Incoming Attributes
    AGGREGATE_TYPE = Homogeneous Collection (If Possible)
    GROUP_BY = sa2_SA22023_V1 transects_globalid fme_feature_type sa2_Exiting_Selected_Transects sa2_HRSS_Transects_to_Schedule sa2_mpi_schedule sa2_New_Transects_Active_to_Validate_HRSS sa2_New_Transects_MPI sa2_OBJECTID sa2_Required_Transects_Active_to_Validate_HRSS sa2_Required_Transects_MPI transects_created_date transects_created_user transects_Crosby transects_Host_Count transects_inspection_date transects_inspection_stage transects_inspection_status transects_last_edited_date transects_last_edited_user transects_objectid transects_personal_security transects_R1_Inspection_Status transects_R2_Inspection_Status transects_R3_Inspection_status transects_Round_1_Date transects_Round_2_Date transects_Round_3_Date transects_rsa_abbreviation transects_SA_Name transects_SA2_Number transects_safety_comments transects_Scheduled_for_Round transects_scheduled_for_round1 transects_scheduled_for_round2 transects_scheduled_for_round3 transects_Shape__Length transects_surveyorid transects_traffic_details transects_transect_comments transects_transect_id transects_transect_status transects_tvd_quality
    LIST_ATTRS_TO_INCLUDE = vegetation_Priority vegetation_host_identity
    LIST_NAME = _list
    MODE = Geometry - Assemble One Level
    SEP = ,
    AGGREGATE -> ListElementCounter [off]
ListElementCounter [off]
    CNT_ATTR = _element_count
    LIST_NAME = _list{}
    -> ListHistogrammer [off]
ListHistogrammer [off]
    LIST_NAME = _histogram
    SRC_LIST = _list{}.vegetation_Priority
    -> ListExploder [off]
ListExploder [off]
    ATTR_ACCUM_MODE = Merge List Attributes
    ATTR_CONFLICT_RES_LOOKUP = INCOMING_IF_CONFLICT
    INDEX_ATTR = _element_index
    LIST_ATTR = _histogram{}
    ATTR_CONFLICT_RES = Use List Attribute Values

Bookmark: SELECT Transects By Priority
Note: Fetch Priority NumberAlpha
StringSearcher_2
    CASE = no
    MATCHED_RESULT_ATTR = vegetation_Priority_Number
    REGEXP = \d+[A-Z]$
    STRING_TO_SEARCH = @Value(vegetation_Priority)
    MATCHED -> StringSearcher_3
    NOT_MATCHED -> StringSearcher
Note: Fetch Priority Alpha
StringSearcher_3
    CASE = no
    MATCHED_RESULT_ATTR = vegetation_Priority_Alpha
    REGEXP = [A-Z]$
    STRING_TO_SEARCH = @Value(vegetation_Priority_Number)
    MATCHED -> StringReplacer
    NOT_MATCHED -> AttributeCreator_31
Note: Replace Alpha from Number attribute
StringReplacer
    CASE = NO
    FIND_TEXT = @Value(vegetation_Priority_Alpha)
    NO_MATCH = _FME_NO_OP_
    REGEXP = NO
    SRC_ATTRS = vegetation_Priority_Number
    -> Sorter
Note: Fetch Priority Number (only)
StringSearcher
    CASE = no
    MATCHED_RESULT_ATTR = vegetation_Priority_Number
    REGEXP = \d+$
    STRING_TO_SEARCH = @Value(vegetation_Priority)
    MATCHED -> AttributeCreator_31
    NOT_MATCHED -> AttributeCreator_10
Note: Alpha = ZZ
AttributeCreator_31
    ATTR_TABLE:
      SET_TO vegetation_Priority_Alpha (varchar(2)) = Z
      SET_TO vegetation_Priority_Number (buffer) = FME_CONDITIONAL:DEFAULT_VALUE'_FME_NO_OP_'BOOL_OP;OR;COMPOSITE_TEST;1;TEST @Value(vegetation_Priority_Number) = 0'100'FME_NUM_CONDITIONS2___
    -> Sorter
Note: Sort By: Priority Number, then Priority Letter, then Inspection Date (Oldest First)
Sorter
    SORT_PARM = vegetation_Priority_Number NUMERIC ASCENDING vegetation_Priority_Alpha ALPHA ASCENDING transects_inspection_date NATURAL ASCENDING
    SORTED -> Sampler_5
Note: Priority = 100
AttributeCreator_10
    ATTR_TABLE = SET_TO vegetation_Priority_Number (uint8) = 100
    -> Sorter_2
Note: Sort By: Inspection Date (Oldest First)
Sorter_2
    SORT_PARM = transects_inspection_date NATURAL ASCENDING
    SORTED -> FeatureHolder
Note: Hold for Highest Priority to Pass
FeatureHolder
    -> Sampler_5
Note: Sample Highest Priority Vegetation per Transect
Sampler_5
    GROUP_BY = transects_globalid
    MODE = ORIGINAL
    RATE = 1
    SAMPLE_TYPE_MULTIPLIER = -1
    SAMPLE_MODE = No
    SAMPLE_TYPE_LONG = First N Features
    SAMPLED -> StatisticsCalculator

Bookmark: Transect Validation
Note: Individual SA2 with Total Transects
StatisticsCalculator
    ATTR_ACCUM_MODE = None
    CALCULATION_MODE = NUMERIC
    FEAT_STATS = sa2_SA22023_V1,NUMERIC_MODE,,,COUNT,,,,,,,,,,
    GROUP_BY = sa2_SA22023_V1 sa2_HRSS_Transects_to_Schedule sa2_New_Transects_MPI sa2_Required_Transects_MPI
    SUMMARY -> StatisticsCalculator_6
    COMPLETE -> FeatureMerger_6 [REQUESTOR]
Note: Sum Req and New Transects
StatisticsCalculator_6
    ATTR_ACCUM_MODE = None
    CALCULATION_MODE = NUMERIC
    FEAT_STATS = sa2_Required_Transects_MPI,NUMERIC_MODE,,,,SUM,,,,,,,,,;sa2_New_Transects_MPI,NUMERIC_MODE,,,,SUM,,,,,,,,,
    GROUP_BY = sa2_HRSS_Transects_to_Schedule
    SUMMARY -> AttributeRenamer_2
Note: Rename to logical attributes
AttributeRenamer_2
    ATTR_TABLE:
      RENAME_SET_DEFAULT sa2_New_Transects_MPI.sum > sa2_New_Transects_Active_to_Validate_HRSS
      RENAME_SET_DEFAULT sa2_Required_Transects_MPI.sum > sa2_Required_Transects_Active_to_Validate_HRSS
    KEEP_RENAMED_ONLY = no
    MISSING_INPUT_ATTRS = REMOVE
    -> FeatureMerger_6 [SUPPLIER]
Note: Merge Req, New Counts
FeatureMerger_6
    ATTR_ACCUM_MODE = Merge Supplier
    ATTR_CONFLICT_RES_LOOKUP = REQUESTOR_IF_CONFLICT
    GROUP_BY = sa2_HRSS_Transects_to_Schedule
    IGNORE_NULLS = No
    JOIN_KEYS = @Value(sa2_New_Transects_Active_to_Validate_HRSS) @Value(sa2_New_Transects_Active_to_Validate_HRSS) AUTO @Value(sa2_Required_Transects_Active_to_Validate_HRSS) @Value(sa2_Required_Transects_Active_to_Validate_HRSS) AUTO
    MERGE_TYPE = Attributes Only
    PROCESS_DUPS = NO
    REJECT_NULL_MISSING_KEYS = No
    SUPPLIERS_FIRST = No
    ATTR_CONFLICT_RES = Use Requestor
    MERGED -> AttributeManager_2
    UNMERGED_REQUESTOR -> AttributeCreator_12
    <REJECTED> -> AttributeCreator_21
Note: FAILED VALIDATION
AttributeCreator_12
    ATTR_TABLE:
      SET_TO errorType (buffer) = Transect Validation Bookmark - FeatureMerger_6 UnmergedRequestor
      SET_TO errorMessage (buffer) = *******************************************


        Data Validation FAILED

        Required Transects: @Value(sa2_Required_Transects_Active_to_Validate_HRSS)
        In-flight Req Transects: @Value(sa2_Required_Transects_MPI)

        New Transects: @Value(sa2_New_Transects_Active_to_Validate_HRSS)
        In-flight New Transects: @Value(sa2_New_Transects_MPI)

        Notify FME Specialist


        *******************************************
    -> Junction_26
Note: Error
AttributeCreator_21
    ATTR_TABLE:
      SET_TO errorType (buffer) = Bookmark: Transect Validation - FeatureMerger_6
      SET_TO errorMessage (buffer) = Error Type: @Value(errorType)
        FME Rejection Code: @Value(fme_rejection_code)

        Notify FME Specialist
    -> Junction_19

Bookmark: AGOL Update - Attribute Cleanup
AttributeKeeper_2
    CREATE_BULK_MODE_FEATURES = NO
    KEEP_ATTRS = Scheduled_for_Round,scheduled_for_round1,scheduled_for_round2,scheduled_for_round3,transects_objectid
    -> AttributeRenamer_4
AttributeRenamer_4
    ATTR_TABLE = RENAME_SET_DEFAULT transects_objectid > objectid
    KEEP_RENAMED_ONLY = no
    MISSING_INPUT_ATTRS = REMOVE
    -> FeatureMerger_9 [SUPPLIER]

Bookmark: Assemble Summary Statistics
Note: Count Final Scheduled
StatisticsCalculator_3
    ATTR_ACCUM_MODE = None
    CALCULATION_MODE = NUMERIC
    FEAT_STATS = sa2_HRSS_Transects_to_Schedule,NUMERIC_MODE,,,COUNT,,,,,,,,,,
    GROUP_BY = sa2_New_Transects_Active_to_Validate_HRSS sa2_Required_Transects_Active_to_Validate_HRSS sa2_HRSS_Transects_to_Schedule
    SUMMARY -> FeatureMerger_11 [REQUESTOR]
Note: Count Final Scheduled - AUTOMATED
StatisticsCalculator_7
    ATTR_ACCUM_MODE = None
    CALCULATION_MODE = NUMERIC
    FEAT_STATS = sa2_HRSS_Transects_to_Schedule,NUMERIC_MODE,,,COUNT,,,,,,,,,,
    GROUP_BY = sa2_New_Transects_Active_to_Validate_HRSS sa2_Required_Transects_Active_to_Validate_HRSS sa2_HRSS_Transects_to_Schedule
    SUMMARY -> AttributeManager
Note: sa2_HRSS_Transects_to_Schedule-AUTOMATED
AttributeManager
    ATTR_TABLE:
      REMOVE sa2_HRSS_Transects_to_Schedule (int32)
      REMOVE sa2_New_Transects_Active_to_Validate_HRSS (real64)
      REMOVE sa2_Required_Transects_Active_to_Validate_HRSS (real64)
      RENAME_SET_VALUE sa2_HRSS_Transects_to_Schedule.total_count > sa2_HRSS_Transects_to_Schedule-AUTOMATED (uint64)
    -> FeatureMerger_11 [SUPPLIER]
FeatureMerger_11
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> FeatureMerger_7 [REQUESTOR]
    <REJECTED> -> AttributeCreator_37
Note: Error
AttributeCreator_37
    ATTR_TABLE:
      SET_TO errorType (buffer) = Bookmark: Assemble Summary Statistics - FeatureMerger_11
      SET_TO errorMessage (buffer) = FME Rejection Code: @Value(fme_rejection_code)

        Check for Duplicate Summary of Final Schedule Counts, then notify FME Specialist
    -> Junction_35

Bookmark: REPORT - Transects with No Vegetation
Note: Format Attributes for Excel Report
AttributeManager_8
    ATTR_TABLE:
      RENAME_SET_VALUE transects_SA2_Number > SA2_Number (real64)
      RENAME_SET_VALUE transects_SA_Name > SA_Name (varchar(256))
      RENAME_SET_VALUE sa2_Required_Transects_MPI > Required_Transects_MPI (uint8)
      RENAME_SET_VALUE sa2_New_Transects_MPI > New_Transects_MPI (varchar(200))
      RENAME_SET_VALUE sa2_Exiting_Selected_Transects > Exiting_Selected_Transects (real64)
      RENAME_SET_VALUE transects_transect_id > Transect_ID (int32)
      RENAME_SET_VALUE transects_transect_comments > Transect_Comments (varchar(1000))
      RENAME_SET_VALUE transects_inspection_date > Transect_Previous_Inspection_Date (int64)
      REMOVE sa2_OBJECTID (int32)
      REMOVE sa2_SA22023_V1 (varchar(6))
      REMOVE transects_objectid (int32)
      REMOVE transects_globalid (varchar(38))
      REMOVE transects_created_user (varchar(255))
      REMOVE transects_created_date (int64)
      REMOVE transects_last_edited_user (varchar(255))
      REMOVE transects_last_edited_date (int64)
      REMOVE transects_scheduled_for_round1 (varchar(255))
      REMOVE transects_scheduled_for_round2 (varchar(255))
      REMOVE transects_scheduled_for_round3 (varchar(255))
      REMOVE transects_transect_status (varchar(255))
      REMOVE transects_rsa_abbreviation (varchar(255))
      REMOVE transects_traffic_details (varchar(255))
      REMOVE transects_personal_security (varchar(255))
      REMOVE transects_safety_comments (varchar(1000))
      REMOVE transects_surveyorid (int32)
      REMOVE transects_inspection_status (varchar(255))
      REMOVE transects_inspection_stage (varchar(255))
      REMOVE transects_tvd_quality (int16)
      REMOVE transects_Round_1_Date (int64)
      REMOVE transects_Round_2_Date (int64)
      REMOVE transects_Round_3_Date (int64)
      REMOVE transects_R1_Inspection_Status (varchar(256))
      REMOVE transects_R2_Inspection_Status (varchar(256))
      REMOVE transects_R3_Inspection_status (varchar(256))
      REMOVE transects_Host_Count (int16)
      REMOVE transects_Crosby (varchar(255))
      REMOVE transects_Scheduled_for_Round (varchar(255))
      REMOVE transects_Shape__Length (real64)
      REMOVE vegetation_parentid (varchar(200))
      REMOVE sa2_HRSS_Transects_to_Schedule (int32)
      REMOVE sa2_New_Transects_Active_to_Validate_HRSS (real64)
      REMOVE sa2_Required_Transects_Active_to_Validate_HRSS (real64)
      REMOVE sa2_mpi_schedule (varchar(200))
    USER_EXPOSED_ATTRIBUTES = sa2_SA2_Transect_Selection_Completed
    -> Sorter_6
Note: Sort by SA2_Number
Sorter_6
    SORT_PARM = SA2_Number NATURAL ASCENDING
    SORTED -> Junction_23

Bookmark: Transect Validation - No Transects in SA2
Note: Sum Req, New Transects for SA2's with no Transects
StatisticsCalculator_4
    ATTR_ACCUM_MODE = None
    CALCULATION_MODE = NUMERIC
    FEAT_STATS = sa2_Required_Transects_MPI,NUMERIC_MODE,,,,SUM,,,,,,,,,;sa2_New_Transects_MPI,NUMERIC_MODE,,,,SUM,,,,,,,,,
    SUMMARY -> AttributeRenamer_3
    COMPLETE -> FeatureMerger_8 [REQUESTOR]
Note: Rename to Logical Attr
AttributeRenamer_3
    ATTR_TABLE:
      RENAME_SET_DEFAULT sa2_New_Transects_MPI.sum > sa2_New_Transects_NoTransects_to_Validate_HRSS
      RENAME_SET_DEFAULT sa2_Required_Transects_MPI.sum > sa2_Required_Transects_NoTransects_to_Validate_HRSS
    KEEP_RENAMED_ONLY = no
    MISSING_INPUT_ATTRS = REMOVE
    -> TestFilter_3
Note: PASS Req = New
TestFilter_3
    DEFAULT_VALUE = <UNFILTERED>
    PASSED_TEST_GROUP_OUTPUT = FIRST
    TEST_LIST = "BOOL_OP,OR,COMPOSITE_TEST,""""""1"""""",TEST_CLAUSE,TEST @Value(sa2_Required_Transects_NoTransects_to_Validate_HRSS) = @Value(sa2_New_Transects_NoTransects_to_Validate_HRSS)",Required-Equals-New
    Required-Equals-New -> FeatureMerger_7 [SUPPLIER]
    <UNFILTERED> -> FeatureMerger_8 [SUPPLIER]
Note: Trigger List if Failed
FeatureMerger_8
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> AttributeCreator_14
    UNMERGED_REQUESTOR -> AttributeManager_6
    <REJECTED> -> AttributeCreator_22
Note: Create CSV
AttributeCreator_14
    ATTR_TABLE = SET_TO _line (varchar(200)) = @Value(sa2_SA22023_V1),@Value(sa2_Required_Transects_MPI),@Value(sa2_New_Transects_MPI)
    -> Aggregator
Note: Create List
Aggregator
    ACCUM_ATTRS_NAME = Drop Incoming Attributes
    AGGREGATE_TYPE = Homogeneous Collection (If Possible)
    CONCAT_ATTRS = _line
    GROUP_BY = sa2_New_Transects_NoTransects_to_Validate_HRSS sa2_Required_Transects_NoTransects_to_Validate_HRSS
    MODE = Geometry - Assemble One Level
    SEP = "\n"
    AGGREGATE -> AttributeCreator_13
Note: FAILED VALIDATION
AttributeCreator_13
    ATTR_TABLE:
      SET_TO errorType (buffer) = Transect Validation - No Transects in SA2 Bookmark - TestFilter_3 Unfiltered
      SET_TO errorMessage (buffer) = *******************************************

        Data Validation FAILED

        In SA2's with no Transects:

        Required Transects = @Value(sa2_Required_Transects_NoTransects_to_Validate_HRSS)
        New Transects = @Value(sa2_New_Transects_NoTransects_to_Validate_HRSS)


        Verify any anomaly SA2 Entries with Required and New Transect Counts (from HRSS). It is likely the actual Transect count does not align with SA2 Transect Count (from SA2 layer).

        SA2 Num,Req,New
        @Value(_line)


        *******************************************
    -> Junction_27
Note: Error
AttributeCreator_22
    ATTR_TABLE:
      SET_TO errorType (buffer) = Bookmark: Transect Validation - No Transects in SA2 - FeatureMerger_8
      SET_TO errorMessage (buffer) = Error Type: @Value(errorType)
        FME Rejection Code: @Value(fme_rejection_code)

        Notify FME Specialist
    -> Junction_20

Bookmark: Transect Validation - Final Counts
FeatureMerger_7
    ATTR_ACCUM_MODE = Merge Supplier
    ATTR_CONFLICT_RES_LOOKUP = REQUESTOR_IF_CONFLICT
    IGNORE_NULLS = No
    JOIN_KEYS = 1 1 AUTO
    MERGE_TYPE = Attributes Only
    PROCESS_DUPS = NO
    REJECT_NULL_MISSING_KEYS = No
    SUPPLIERS_FIRST = No
    ATTR_CONFLICT_RES = Use Requestor
    MERGED -> TestFilter_8
    MERGED -> Junction_34
    UNMERGED_REQUESTOR -> Junction_34
    <REJECTED> -> AttributeCreator_23
TestFilter_8
    DEFAULT_VALUE = FAIL
    PASSED_TEST_GROUP_OUTPUT = FIRST
    TEST_LIST = "BOOL_OP,AND,COMPOSITE_TEST,""""""1"""""",TEST_CLAUSE,TEST @Value(sa2_HRSS_Transects_to_Schedule) = @Evaluate(@Value(sa2_HRSS_Transects_to_Schedule.total_count)+@Value(sa2_New_Transects_Active_to_Validate_HRSS)+@Value(sa2_Required_Transects_NoTransects_to_Validate_HRSS)+@Value(sa2_HRSS_Transects_to_Schedule-AUTOMATED))",PASS
    PASS -> AttributeKeeper_4
    FAIL -> AttributeCreator_15
Note: Trigger for Final Write
AttributeKeeper_4
    CREATE_BULK_MODE_FEATURES = NO
    -> FeatureMerger_10 [SUPPLIER]
Note: FAILED VALIDATION
AttributeCreator_15
    ATTR_TABLE:
      SET_TO errorType (buffer) = Transect Validation - Final Counts Bookmark - TestFilter_8 FAIL
      SET_TO errorMessage (buffer) = *******************************************

        Data Validation FAILED

        Final Transect Validation Counts

        HRSS Required Transects = @Value(sa2_HRSS_Transects_to_Schedule)

        Final (proposed) Scheduled Transect Count: @Value(sa2_HRSS_Transects_to_Schedule.total_count)
        Final (proposed) New Transects = @Value(sa2_New_Transects_Active_to_Validate_HRSS)

        No Transects in SA2 Count: @Value(sa2_Required_Transects_NoTransects_to_Validate_HRSS)

        Notify FME Specialist

        *******************************************
    -> Junction_31
Note: Error
AttributeCreator_23
    ATTR_TABLE:
      SET_TO errorType (buffer) = Bookmark: Transect Validation - Final Counts - FeatureMerger_7
      SET_TO errorMessage (buffer) = Error Type: @Value(errorType)
        FME Rejection Code: @Value(fme_rejection_code)

        Notify FME Specialist
    -> Junction_21

Bookmark: Create Description
AttributeKeeper_5
    CREATE_BULK_MODE_FEATURES = NO
    -> AttributeManager_3
AttributeManager_3
    ATTR_TABLE:
      SET_TO HRSS_Transects_to_Schedule (varchar(66)) = Total number of Transects from MPI to be scheduled for this round.
      SET_TO Required_Transects_SA2_Active (varchar(71)) = Number of Transects required in Active SA2 areas in the SPS Biota data.
      SET_TO New_Transects_SA2_Active (varchar(73)) = Number of New Transects needed in Active SA2 areas in the SPS Biota data.
      SET_TO HRSS_Transects_Scheduled (varchar(85)) = Number of Transects Scheduled (P1, P2, P3) in Active SA2 areas in the SPS Biota data.
      SET_TO Required_Transects_NoTransects_Available (varchar(62)) = Number of Transects from MPI in an SA2 area with No Transects.
      SET_TO New_Transects_NoTransects_Available (varchar(64)) = Number of New Transects needed in an SA2 area with No Transects.
      SET_TO HRSS_Transects_to_Schedule-MANUAL (varchar(59)) = Number of New Transects for SPS Biota to Manually Schedule.
      SET_TO All_Transects_Required (varchar(41)) = Total required transects. Columns C+D+E+G
      SET_TO Transects_Available_PLUS_Req_New_Transects (varchar(68)) = Pool of transects available plus required new transects. Columns B+F
    -> Junction_36
